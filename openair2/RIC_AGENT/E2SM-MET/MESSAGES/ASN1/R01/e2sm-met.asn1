-- ASN1START
-- **************************************************************
-- E2SM-MET 2.0.1 Information Element Definitions
-- **************************************************************

E2SM-MET-IEs {
    iso(1) identified-organization(3) dod(6) internet(1) private(4) enterprise(1) oran(53148) e2(1) version2(2) e2sm(2) e2sm-METMON-IEs (98)}
    DEFINITIONS AUTOMATIC TAGS ::= 
    
    BEGIN
    
    TimeStamp ::= OCTET STRING (SIZE(4))
    
    -- **************************************************************
    
    CellObjectID ::= INTEGER (0.. 255)
    
    GranularityPeriod ::= INTEGER (1.. 4294967295)
    
    SubscriptionID ::= INTEGER (1.. 4294967295)
    
    -- **************************************************************
    
    GlobalMETnode-ID ::= INTEGER (1.. 4294967295)
    
    -- **************************************************************
    
    RANfunction-Name ::= SEQUENCE{
        ranFunction-ShortName		PrintableString(SIZE(1..150,...)),
        ranFunction-E2SM-OID		PrintableString(SIZE(1..1000,...)),
        ranFunction-Description		PrintableString(SIZE(1..150,...)),
        ...
    }
    
    -- **************************************************************
    --   Lists
    -- **************************************************************
    
    
    -- ****************** 
    -- UE related defs 
    maxofUE             		INTEGER ::= 65535
    
    UEID ::= INTEGER (0.. 255)
    
    UETag ::= PrintableString(SIZE(1.. 150))
    
    UEItem ::= SEQUENCE {
        ueID	UEID,
        ueTag   UETag   OPTIONAL,
        ...
    }
    
    --****************
    
    MeasurementInfoList ::= SEQUENCE (SIZE(1..65535)) OF MeasurementInfoItem

    MeasurementInfoItem::= PrintableString(SIZE(1.. 150))
    
    MeasurementData ::= SEQUENCE (SIZE(1..65535)) OF MeasurementRecord
    
    MeasurementRecord ::= SEQUENCE {
        ueID					UEID,
        ueTag                   UETag,
        measRecordItemList      MeasurementRecordItemList,
        ...
    }

    MeasurementRecordItemList ::= SEQUENCE (SIZE(1..65535)) OF MeasurementRecordItem
    
    MeasurementRecordItem ::= PrintableString(SIZE(1.. 150))
    
    MeasurementInfo-Action-List ::= SEQUENCE (SIZE(1..65535)) OF MeasurementInfo-Action-Item
    
    MeasurementInfo-Action-Item ::= SEQUENCE {
        measName				MeasurementTypeName,
        measID					MeasurementTypeID				OPTIONAL,
        ...
    }
    
    MeasurementTypeName ::= PrintableString(SIZE(1.. 150))
    
    MeasurementTypeID ::= INTEGER (1.. 65535, ...)
    
    -- **************************************************************
    -- E2SM-MET Service Model IEs
    -- **************************************************************
    
    -- **************************************************************
    --   Event Trigger Definition OCTET STRING contents
    -- **************************************************************
    
    E2SM-MET-EventTriggerDefinition ::= SEQUENCE{
        eventDefinition-formats			CHOICE{
            eventDefinition-Format1			E2SM-MET-EventTriggerDefinition-Format1,
            ...
        },
        ...
    }
    
    E2SM-MET-EventTriggerDefinition-Format1 ::= SEQUENCE{
        reportingPeriod					INTEGER (1.. 4294967295),
        ...
    }
    
    -- **************************************************************
    --   Action Definition OCTET STRING contents
    -- **************************************************************
        
    E2SM-MET-ActionDefinition ::= SEQUENCE{
        ric-Style-Type					RIC-Style-Type,
        actionDefinition-formats 	CHOICE{
            actionDefinition-Format1		E2SM-MET-ActionDefinition-Format1,
            ...
        },
        ...
    }
    
    E2SM-MET-ActionDefinition-Format1 ::= SEQUENCE {
        cellObjID						CellObjectID,
        measInfoList					MeasurementInfoList,
        granulPeriod					GranularityPeriod,
        subscriptID						SubscriptionID,
        ...
    }
    
    -- **************************************************************
    --   Indication Header OCTET STRING contents
    -- **************************************************************
    
    E2SM-MET-IndicationHeader ::= SEQUENCE{
        indicationHeader-formats		CHOICE{
            indicationHeader-Format1		E2SM-MET-IndicationHeader-Format1,
            ...
        },
        ...
    }
    
    E2SM-MET-IndicationHeader-Format1 ::= SEQUENCE{
        colletStartTime					TimeStamp,
        measInfoList					MeasurementInfoList,
        fileFormatversion				PrintableString (SIZE (0..15), ...)		OPTIONAL,
        senderName						PrintableString (SIZE (0..400), ...)	OPTIONAL,
        metNodeID						GlobalMETnode-ID						OPTIONAL,
        ...
    }
    
    -- **************************************************************
    --   Indication Message OCTET STRING contents
    -- **************************************************************
    
    E2SM-MET-IndicationMessage ::= SEQUENCE{
        indicationMessage-formats		CHOICE{
            indicationMessage-Format1		E2SM-MET-IndicationMessage-Format1,
            ...
        },
        ...
    }
    
    E2SM-MET-IndicationMessage-Format1 ::= SEQUENCE {
        subscriptID						SubscriptionID,
        cellObjID						CellObjectID							OPTIONAL,
        granulPeriod					GranularityPeriod 						OPTIONAL,
        measInfoList					MeasurementInfoList						OPTIONAL,
        measData						MeasurementData,
        ...
    }
    
    -- ***************************************************************
    --   RAN Function Definition OCTET STRING contents
    -- ***************************************************************
    
    E2SM-MET-RANfunction-Description ::= SEQUENCE{
        ranFunction-Name				RANfunction-Name,
        ric-EventTriggerStyle-List		SEQUENCE (SIZE(1..255)) OF RIC-EventTriggerStyle-Item 		OPTIONAL,
        ric-ReportStyle-List			SEQUENCE (SIZE(1..255)) OF RIC-ReportStyle-Item 			OPTIONAL,
        ...
    }
    
    RIC-Style-Type ::= INTEGER (0.. 255, ...)

    RIC-Style-Name ::= PrintableString(SIZE(1.. 150, ...))
    
    RIC-Format-Type ::= INTEGER (0.. 255, ...)
    
    RIC-EventTriggerStyle-Item ::= SEQUENCE{
        ric-EventTriggerStyle-Type			RIC-Style-Type,
        ric-EventTriggerStyle-Name			RIC-Style-Name,
        ric-EventTriggerFormat-Type			RIC-Format-Type,
        ...
    }
    
    RIC-ReportStyle-Item ::= SEQUENCE{
        ric-ReportStyle-Type				RIC-Style-Type,
        ric-ReportStyle-Name				RIC-Style-Name,
        ric-ActionFormat-Type				RIC-Format-Type,
        measInfo-Action-List				MeasurementInfo-Action-List, 
        ric-IndicationHeaderFormat-Type		RIC-Format-Type,
        ric-IndicationMessageFormat-Type	RIC-Format-Type,
        ...
    }
        
    END
    
    -- ASN1STOP
