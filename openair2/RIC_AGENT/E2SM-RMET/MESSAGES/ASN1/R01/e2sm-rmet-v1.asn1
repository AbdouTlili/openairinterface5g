-- ASN1START
-- **************************************************************
-- E2SM-RMET 2.0.1 Information Element Definitions
-- **************************************************************

E2SM-RMET-IEs {
iso(1) identified-organization(3) dod(6) internet(1) private(4) enterprise(1) oran(53148) e2(1) version2(2) e2sm(2) e2sm-RMET-IEs (99)}

DEFINITIONS AUTOMATIC TAGS ::= 

BEGIN

-- **************************************************************
--   IEs
-- **************************************************************

PLMN-Identity ::= OCTET STRING (SIZE(3))

EUTRACellIdentity ::= BIT STRING (SIZE(28))

NRCellIdentity ::= BIT STRING (SIZE(36))

EUTRACGI ::= SEQUENCE {
	pLMN-Identity			PLMN-Identity,
	eUTRACellIdentity		EUTRACellIdentity,
	...
}

NRCGI ::= SEQUENCE {
	pLMN-Identity			PLMN-Identity,
	nRCellIdentity			NRCellIdentity,
	...
}

CellGlobalID ::= CHOICE {
	nr-CGI					NRCGI,
	eUTRA-CGI				EUTRACGI,
	...
}

SNSSAI ::= SEQUENCE {
	sST						OCTET STRING (SIZE(1)),
	sD						OCTET STRING (SIZE(3)) 		OPTIONAL,
	...
}

FiveQI ::= INTEGER (0.. 255, ...)

QCI ::= INTEGER (0.. 255, ...)

ARP ::= INTEGER (1.. 15, ...)

TimeStamp ::= OCTET STRING (SIZE(4))

-- **************************************************************

CellObjectID ::= PrintableString(SIZE (0.. 400), ...)

GranularityPeriod ::= INTEGER


MeasurementTypeName ::= PrintableString(SIZE(1.. 150, ...))

MeasurementTypeID ::= INTEGER (1.. 65536, ...)


SubscriptionID ::= INTEGER (1.. 4294967296, ...)

-- **************************************************************

GlobalRMETnode-ID ::= CHOICE{
	gNB						GlobalRMETnode-gNB-ID,
	en-gNB					GlobalRMETnode-en-gNB-ID,
	ng-eNB					GlobalRMETnode-ng-eNB-ID,
	eNB						GlobalRMETnode-eNB-ID,
	...
}

GlobalRMETnode-gNB-ID ::= SEQUENCE{
	global-gNB-ID			GlobalgNB-ID,
	gNB-CU-UP-ID			GNB-CU-UP-ID					OPTIONAL,
	gNB-DU-ID				GNB-DU-ID						OPTIONAL,
	...
}

GlobalgNB-ID	::= SEQUENCE {
	plmn-id					PLMN-Identity,
	gnb-id					GNB-ID-Choice,
	...
}

GNB-CU-UP-ID ::= 	INTEGER (0..68719476735)

GNB-DU-ID ::=  INTEGER (0..68719476735)

GNB-ID-Choice ::= CHOICE {
	gnb-ID					BIT STRING (SIZE(22..32)),
	...
}

GlobalRMETnode-en-gNB-ID ::= SEQUENCE{
	global-gNB-ID			GlobalenGNB-ID,
	gNB-CU-UP-ID			GNB-CU-UP-ID					OPTIONAL,
	gNB-DU-ID				GNB-DU-ID						OPTIONAL,
	...
}

GlobalenGNB-ID ::= SEQUENCE {
	pLMN-Identity			PLMN-Identity,
	gNB-ID					ENGNB-ID,
	...
}

ENGNB-ID ::= CHOICE {
	gNB-ID					BIT STRING (SIZE (22..32)),
	...
}

GlobalRMETnode-ng-eNB-ID ::= SEQUENCE{
	global-ng-eNB-ID		GlobalngeNB-ID,
	gNB-DU-ID				GNB-DU-ID						OPTIONAL,
	...
}

GlobalngeNB-ID ::= SEQUENCE {
	plmn-id					PLMN-Identity,
	enb-id					ENB-ID-Choice,
	short-Macro-eNB-ID		BIT STRING (SIZE(18)),
	long-Macro-eNB-ID		BIT STRING (SIZE(21)),
	...
}

ENB-ID-Choice ::= CHOICE {
	enb-ID-macro			BIT STRING (SIZE(20)),
	enb-ID-shortmacro		BIT STRING (SIZE(18)),
	enb-ID-longmacro		BIT STRING (SIZE(21)),
	...
}

GlobalRMETnode-eNB-ID ::= SEQUENCE{
	global-eNB-ID			GlobalENB-ID,
	...
}

GlobalENB-ID ::= SEQUENCE {
	pLMN-Identity			PLMN-Identity,
	eNB-ID					ENB-ID,
	...
}

ENB-ID ::= CHOICE {
	macro-eNB-ID			BIT STRING (SIZE (20)),
	home-eNB-ID				BIT STRING (SIZE (28)),
	...
}	

-- **************************************************************

RANfunction-Name ::= SEQUENCE{
	ranFunction-ShortName		PrintableString(SIZE(1..150,...)),
	ranFunction-E2SM-OID		PrintableString(SIZE(1..1000,...)),
	ranFunction-Description		PrintableString(SIZE(1..150,...)),
	ranFunction-Instance		INTEGER 					OPTIONAL,
	...
}

RIC-Style-Type ::= INTEGER

RIC-Style-Name ::= PrintableString(SIZE(1.. 150, ...))

RIC-Format-Type ::= INTEGER


MeasName ::= PrintableString(SIZE(1.. 150, ...))
MeasId ::= INTEGER

-- **************************************************************
--   Lists
-- **************************************************************

maxnoofRMETNodes				INTEGER ::= 1024
maxnoofCells				INTEGER ::= 16384
maxnoofRICStyles			INTEGER ::= 63
maxnoofMeasurementInfo		INTEGER ::= 65536
maxnoofMeasurementRecord	INTEGER ::= 65536
maxnoofMeasurementValue		INTEGER ::= 2147483647

MeasurementInfoList ::= SEQUENCE (SIZE(1..maxnoofMeasurementInfo)) OF MeasurementInfoItem

MeasurementInfoItem ::= CHOICE {
	measID					MeasurementTypeID,
	measName				MeasurementTypeName,
	
	...
}

MeasurementData ::= SEQUENCE (SIZE(1..maxnoofMeasurementRecord)) OF MeasurementRecordItem

MeasurementRecordItem ::= CHOICE {
	integer					INTEGER,
	real					REAL,
	noValue					NULL,
	...
}		


-- **************************************************************
-- E2SM-RMET Service Model IEs
-- **************************************************************

-- **************************************************************
--   Event Trigger Definition OCTET STRING contents
-- **************************************************************

E2SM-RMET-EventTriggerDefinition ::= SEQUENCE{
	eventDefinition-formats			CHOICE{
		eventDefinition-Format1			E2SM-RMET-EventTriggerDefinition-Format1,
		...
	},
	...
}

E2SM-RMET-EventTriggerDefinition-Format1 ::= SEQUENCE{
	reportingPeriod					INTEGER,
	...
}

-- **************************************************************
--   Action Definition OCTET STRING contents
-- **************************************************************

E2SM-RMET-ActionDefinition ::= SEQUENCE{
	ric-Style-Type					RIC-Style-Type,
	actionDefinition-formats 	CHOICE{
		actionDefinition-Format1		E2SM-RMET-ActionDefinition-Format1,
		...
	},
	...
}

E2SM-RMET-ActionDefinition-Format1 ::= SEQUENCE {
	cellObjID						CellObjectID,
	measInfoList					MeasurementInfoList,
	granulPeriod					GranularityPeriod,
	subscriptID						SubscriptionID,
	...
}

-- **************************************************************
--   Indication Header OCTET STRING contents
-- **************************************************************

E2SM-RMET-IndicationHeader ::= SEQUENCE{
	indicationHeader-formats		CHOICE{
		indicationHeader-Format1		E2SM-RMET-IndicationHeader-Format1,
		...
	},
	...
}

E2SM-RMET-IndicationHeader-Format1 ::= SEQUENCE{
	colletStartTime					TimeStamp,
	fileFormatversion				PrintableString (SIZE (0..15), ...)		OPTIONAL,
	senderName						PrintableString (SIZE (0..400), ...)	OPTIONAL,
	senderType						PrintableString (SIZE (0..8), ...)		OPTIONAL,
	vendorName						PrintableString (SIZE (0..32), ...)		OPTIONAL,
	rmetNodeID						GlobalRMETnode-ID						OPTIONAL,
	...
}

-- **************************************************************
--   Indication Message OCTET STRING contents
-- **************************************************************

E2SM-RMET-IndicationMessage ::= SEQUENCE{
	indicationMessage-formats		CHOICE{
		indicationMessage-Format1		E2SM-RMET-IndicationMessage-Format1,
		...
	},
	...
}

E2SM-RMET-IndicationMessage-Format1 ::= SEQUENCE {
	subscriptID						SubscriptionID,
	cellObjID						CellObjectID							OPTIONAL,
	granulPeriod					GranularityPeriod 						OPTIONAL,
	measInfoList					MeasurementInfoList						OPTIONAL,
	measData						MeasurementData,
	...
}

-- ***************************************************************
--   RAN Function Definition OCTET STRING contents
-- ***************************************************************

E2SM-RMET-RANfunction-Description ::= SEQUENCE{
	ranFunction-Name				RANfunction-Name,
	ric-RMET-Node-List				SEQUENCE (SIZE(1..maxnoofRMETNodes)) OF RIC-RMETNode-Item 				OPTIONAL,
	ric-EventTriggerStyle-List		SEQUENCE (SIZE(1..maxnoofRICStyles)) OF RIC-EventTriggerStyle-Item 		OPTIONAL,
	ric-ReportStyle-List			SEQUENCE (SIZE(1..maxnoofRICStyles)) OF RIC-ReportStyle-Item 			OPTIONAL,
	...
}

RIC-RMETNode-Item ::= SEQUENCE {
	ric-RMETNode-Type					GlobalRMETnode-ID,
	cell-Measurement-Object-List		SEQUENCE (SIZE(1..maxnoofCells)) OF Cell-Measurement-Object-Item 		OPTIONAL,
	...
}

Cell-Measurement-Object-Item ::= SEQUENCE {
	cell-object-ID						CellObjectID,
	cell-global-ID						CellGlobalID,
	...
}

RIC-EventTriggerStyle-Item ::= SEQUENCE{
	ric-EventTriggerStyle-Type			RIC-Style-Type,
	ric-EventTriggerStyle-Name			RIC-Style-Name,
	ric-EventTriggerFormat-Type			RIC-Format-Type,
	...
}

RIC-ReportStyle-Item ::= SEQUENCE{
	ric-ReportStyle-Type				RIC-Style-Type,
	ric-ReportStyle-Name				RIC-Style-Name,
	ric-ActionFormat-Type				RIC-Format-Type,
	measInfo-Action-List			MeasurementInfoList,
	ric-IndicationHeaderFormat-Type		RIC-Format-Type,
	ric-IndicationMessageFormat-Type	RIC-Format-Type,
	...
}

END

-- ASN1STOP
